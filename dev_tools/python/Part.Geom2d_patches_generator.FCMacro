def text(x, y, text):
    return "#X text %i %i %s;\n" %(x, y , text)

def simple_obj(x, y, typ):
    return "#X obj %i %i %s;\n" %(x, y, typ)

def trigger_ab(x, y, count):
    return  "#X obj %i %i t a %s;\n" %(x, y, "b " * count)

def connect(id1, outlet, id2, inlet):
    return "#X connect %i %i %i %i;\n" %(id1, outlet, id2, inlet)

import inspect
def get_parameters(func):
    try :
        clean_params = list(inspect.signature(func).parameters.keys())
    except ValueError:
        #parse __doc__
        docstr = func.__doc__
        if docstr:
            leftpar = docstr.find("(")+1
            rightpar = docstr.find(")", leftpar)
            paramstr = docstr[leftpar:rightpar]
            paramstr = paramstr.replace("[","")
            paramstr = paramstr.replace("]","")
            paramstr = paramstr.replace("\n","")
            params = paramstr.split(",")
            clean_params = []
            for p in params:
                e=p.find("=")
                if e>0:
                    p = p[:e]
                clean_params.append(p)
        else:
            raise ValueError("no signature nor __doc__ ")
    return clean_params

def getCleanDoc(func):
        docstr = func.__doc__
        dash = docstr.find("--")+3
        return docstr[dash:].replace(",", " \, ").replace("\n", " \; ")

def generate(dirname, what):
    func_list = inspect.getmembers(what, inspect.isroutine)
    for func_name, func in func_list:
        if not func_name.startswith("_"):
            pdname = func_name #.replace("make","")
            params = get_parameters(func)
            if not params:
                Log("%s have no parameters, skipped\n" % pdname)
                continue
            pcount = len(params)
            cnv = "#N canvas 750 350 500 500 12;"           #obj id
            cnv += text(10, 10, params[0])                  # 0
            cnv += simple_obj(10, 30, "inlet")                  # 1
            if pcount > 1:
                cnv += trigger_ab(10, 60, pcount-1)         # 2
                for i, p in enumerate(params[1:]):
                    cnv += text(100*(i+1), 10, p)           # 3+4*i
                    cnv += simple_obj(100*(i+1), 30, "inlet")   # 4+4*i
                    cnv += simple_obj(100*(i+1), 90+30*i, "any")    # 5+4*i
                    cnv += simple_obj(100*(i+1), 120+30*i, "list append")   # 6+4*i

            cnv += simple_obj(10, 300, "list prepend Part %s" %pdname ) # 3+4*(pcount-1) or 2 = last +1
            cnv += simple_obj(10, 330, "fc_process 0")          # 4+4*(pcount-1) or 3 = last +2
            cnv += simple_obj(10, 360, "route ERROR")           # 5+4*(pcount-1) or 4 = last +3
            cnv += simple_obj(10, 390, "print FreeCAD Error")   # 6+4*(pcount-1) or 5 = last +4
            cnv += simple_obj(120, 390, "outlet")               # 7+4*(pcount-1) or 6 = last +5

            cnv += connect(1, 0, 2, 0)
            last = 1
            if  pcount > 1:
                for i in range(pcount-1):
                    cnv += connect(2, i+1, 5+4*i, 0)
                    cnv += connect(4+4*i, 0, 5+4*i, 1)
                    cnv += connect(5+4*i, 0, 6+4*i, 1)
                    if i==0:
                        cnv += connect(2, 0, 6+4*i, 0)
                    else:
                        cnv += connect(6+4*(i-1), 0, 6+4*i, 0)
                last = 2+4*(pcount-1)
                cnv += connect(last, 0, last+1, 0)
            cnv += connect(last+1, 0, last+2, 0)
            cnv += connect(last+2, 0, last+3, 0)
            cnv += connect(last+3, 0, last+4, 0)
            cnv += connect(last+3, 1, last+5, 0)
            import os
            with open(os.path.join(dirname, pdname) + ".pd", 'w') as file:
                file.write(cnv)

def generateHelp(dirname, what):
    func_list = inspect.getmembers(what, inspect.isroutine)
    index=[]
    for func_name, func in func_list:
        if not func_name.startswith("_"):
            pdname = func_name #.replace("make","")
            params = get_parameters(func)
            if not params:
                continue
            pcount = len(params)
            hlp = "#N canvas 436 36 550 620 10;\n"
            hlp +="#X obj 0 0 cnv 15 550 40 empty empty part/%s 3 12 0 18 #c4dcdc #000000 0;\n" % pdname
            hlp +=simple_obj(400, 10, "part/%s" %pdname)
            # DESC
            doc = getCleanDoc(func)
            hlp += text(10, 50, doc)
            index.append(('part/%s' %pdname, doc.split("\;")[0]))
            # INLETS
            hlp +="#X obj 0 180 cnv 3 550 3 empty empty inlets 8 12 0 13 #dcdcdc #000000 0;\n"
            for i, p in enumerate(params):
                hlp +="#X obj 78 %i cnv 17 3 17 empty \$0-pddp.cnv.let.1 %i 5 9 0 16 #dcdcdc #9c9c9c 0;\n" % (200 + 30*i, i)
                hlp += text(100, 200 + 30*i, p)
            # OUTLETS
            hlp +="#X obj 0 %i cnv 3 550 3 empty empty outlets 8 12 0 13 #dcdcdc #000000 0;\n" % (200 + 30*pcount)
            hlp +="#X obj 78 %i cnv 17 3 17 empty empty 0 5 9 0 16 #dcdcdc #9c9c9c 0;\n" % (230 + 30*pcount)
            hlp += text(100, 230 + 30*pcount, "Name of the created FreeCAD object")
            # ARGUMENTS
            hlp +="#X obj 0 %i cnv 3 550 3 empty empty arguments 8 12 0 13 #dcdcdc #000000 0;\n" % (290 + 30*pcount)
            # MORE INFO
            hlp +="#X obj 0 %i cnv 3 550 3 empty empty more_info 8 12 0 13 #dcdcdc #000000 0;\n" % (350 + 30*pcount)
            hlp += text(10, 380 + 30*pcount, "This object is in the ")
            hlp += simple_obj(140, 380 + 30*pcount," helplink part")
            hlp += text(175, 380 + 30*pcount, " part of the ")
            hlp += simple_obj(245, 380 + 30*pcount," helplink FCPD")
            hlp += text(275, 380 + 30*pcount, " library.")
            # FOOTER
            hlp +="#X obj 0 %i cnv 15 550 15 empty empty empty 20 12 0 14 #dcdcdc #404040 0;\n" % (410 + 30*pcount if pcount>6 else 600)

            import os
            with open(os.path.join(dirname, pdname) + "-help.pd", 'w') as file:
                file.write(hlp)

        # INDEX
        hlp = "#N canvas 436 36 600 620 10;\n"
        hlp +=simple_obj(0, 0, "cnv 15 600 40 empty empty part_index 3 12 0 18 #c4dcdc #000000 0")
        for i,(f,d) in enumerate(index):
            hlp +=simple_obj(10, 50+30*i, f)
            hlp += text(200, 50+30*i, d)
        import os
        with open(os.path.join(dirname, os.path.join("..", "part-help.pd")), 'w') as file:
            file.write(hlp)

def main():
    what = Part.Geom2d
    where = os.path.realpath(os.path.join(os.path.dirname(__file__),"../pdlib/geom2d"))
    generate(where, what)
    Msg("Pure-Data patches for Part.Geom2d have been written in %s\n" %where)

    where = os.path.realpath(os.path.join(os.path.dirname(__file__),"../pdhelp/geom2d"))
    generateHelp(where, what)
    Msg("Pure-Data help for Partt.Geom2d have been written in %s\n" %where)

main()
