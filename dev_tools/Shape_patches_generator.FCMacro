def text(x, y, text):
    return "#X text %i %i %s;\n" %(x, y , text)

def simple_obj(x, y, typ):
    return "#X obj %i %i %s;\n" %(x, y, typ)

def trigger_ab(x, y, count):
    return  "#X obj %i %i t a %s;\n" %(x, y, "b " * count)

def connect(id1, outlet, id2, inlet):
    return "#X connect %i %i %i %i;\n" %(id1, outlet, id2, inlet)

import inspect

def get_parameters(func):
    clean_params = None
    try :
        clean_params = list(inspect.signature(func).parameters.keys())
    except ValueError:
        #parse __doc__
        docstr = "\n".join(func.__doc__.split('\n')[1:]) # remove first line
        if docstr:
            leftpar = docstr.find("(")+1
            rightpar = docstr.find(")", leftpar)
            if rightpar>0:
	            paramstr = docstr[leftpar:rightpar]
	            paramstr = paramstr.replace("[","")
	            paramstr = paramstr.replace("]","")
	            paramstr = paramstr.replace("\n","")
	            params = paramstr.split(",")

            else:
                params=[]
            clean_params = []
            for p in params:
                e=p.find("=")
                if e>0:
                    p = p[:e]
                p = p.strip()
                if p:
                    clean_params.append(p)
        else:
            Log("no signature nor __doc__ for %s\n" % func.__name__)
    return clean_params

def getCleanDoc(func):
        ''' return PD printable func.__doc__'''
        docstr = func.__doc__
        dash = docstr.find("--")+2
        docLines = docstr.split("\n")
        if dash > 1:
            docStart = docLines[0]
            docEnd = docstr[dash:]
            docstr = docStart + docEnd
        else:
            docstr = docLines[0]
        return docstr.replace(",", " \, ").replace("\n", " \; ")

def generate(dirname):
    func_list = inspect.getmembers(Part.Shape, inspect.isroutine)
    for func_name, func in func_list:
        if not func_name.startswith("_"):
            pdname = func_name
            params = get_parameters(func)
            if params is None:
                Log("%s have no parameters, skipped\n" % pdname)
                continue
            params = ["Shape"] + params
            pcount = len(params)
            cnv = "#N canvas 750 350 500 500 12;"           #obj id
            cnv += text(10, 10, params[0])                  # 0
            cnv += simple_obj(10, 30, "inlet")                  # 1
            if pcount > 1:
                cnv += trigger_ab(10, 60, pcount-1)         # 2
                for i, p in enumerate(params[1:]):
                    cnv += text(100*(i+1), 10, p)           # 3+4*i
                    cnv += simple_obj(100*(i+1), 30, "inlet")   # 4+4*i
                    cnv += simple_obj(100*(i+1), 90+30*i, "any")    # 5+4*i
                    cnv += simple_obj(100*(i+1), 120+30*i, "list append")   # 6+4*i

            cnv += simple_obj(10, 300, "list prepend Shape %s" %pdname ) # 3+4*(pcount-1) or 2 = last +1
            cnv += simple_obj(10, 330, "fc_process 1")          # 4+4*(pcount-1) or 3 = last +2
            cnv += simple_obj(10, 360, "route ERROR")           # 5+4*(pcount-1) or 4 = last +3
            cnv += simple_obj(10, 390, "print FreeCAD Error")   # 6+4*(pcount-1) or 5 = last +4
            cnv += simple_obj(120, 390, "outlet")               # 7+4*(pcount-1) or 6 = last +5

            cnv += connect(1, 0, 2, 0)
            last = 1
            if  pcount > 1:
                for i in range(pcount-1):
                    cnv += connect(2, i+1, 5+4*i, 0)
                    cnv += connect(4+4*i, 0, 5+4*i, 1)
                    cnv += connect(5+4*i, 0, 6+4*i, 1)
                    if i==0:
                        cnv += connect(2, 0, 6+4*i, 0)
                    else:
                        cnv += connect(6+4*(i-1), 0, 6+4*i, 0)
                last = 2+4*(pcount-1)
                cnv += connect(last, 0, last+1, 0)
            cnv += connect(last+1, 0, last+2, 0)
            cnv += connect(last+2, 0, last+3, 0)
            cnv += connect(last+3, 0, last+4, 0)
            cnv += connect(last+3, 1, last+5, 0)
            import os
            with open(os.path.join(dirname, pdname) + ".pd", 'w') as file:
                file.write(cnv)

def generateHelp(dirname):
    func_list = inspect.getmembers(Part.Shape, inspect.isroutine)
    index=[]
    for func_name, func in func_list:
        if not func_name.startswith("_"):
            pdname = func_name
            params = get_parameters(func)
            if not params:
                continue
            params = ["Shape"] + params
            pcount = len(params)
            hlp = "#N canvas 436 36 550 620 10;\n"
            hlp +="#X obj 0 0 cnv 15 550 40 empty empty shape/%s 3 12 0 18 #c4dcdc #000000 0;\n" % pdname
            hlp +=simple_obj(400, 10, "shape/%s" %pdname)
            # DESC
            doc = getCleanDoc(func)
            hlp += text(10, 50, doc)
            index.append(('shape/%s' %pdname, doc.split("\;")[0]))
            descHeight = 50 + 20 * len(doc.split("\;"))
            # INLETS
            hlp +="#X obj 0 %i cnv 3 550 3 empty empty inlets 8 12 0 13 #dcdcdc #000000 0;\n" % descHeight
            for i, p in enumerate(params):
                hlp +="#X obj 78 %i cnv 17 3 17 empty \$0-pddp.cnv.let.%i %i 5 9 0 16 #dcdcdc #9c9c9c 0;\n" % (descHeight + 20 + 30*i, i, i)
                hlp += text(100, descHeight + 20 + 30*i, p)
            # OUTLETS
            hlp +="#X obj 0 %i cnv 3 550 3 empty empty outlets 8 12 0 13 #dcdcdc #000000 0;\n" % (descHeight + 20 + 30*pcount)
            hlp +="#X obj 78 %i cnv 17 3 17 empty empty 0 5 9 0 16 #dcdcdc #9c9c9c 0;\n" % (descHeight + 50 + 30*pcount)
            hlp += text(100, descHeight + 50 + 30*pcount, "Result of the operation")
            # ARGUMENTS
            hlp +="#X obj 0 %i cnv 3 550 3 empty empty arguments 8 12 0 13 #dcdcdc #000000 0;\n" % (descHeight + 110 + 30*pcount)
            # MORE INFO
            hlp +="#X obj 0 %i cnv 3 550 3 empty empty more_info 8 12 0 13 #dcdcdc #000000 0;\n" % (descHeight + 170 + 30*pcount)
            hlp += text(10, descHeight + 190 + 30*pcount, "This object is in the ")
            hlp += simple_obj(140, descHeight + 190 + 30*pcount," helplink shape")
            hlp += text(175, descHeight + 190 + 30*pcount, " part of the ")
            hlp += simple_obj(245, descHeight + 190 + 30*pcount," helplink FCPD")
            hlp += text(275, descHeight + 190 + 30*pcount, " library.")
            # FOOTER
            hlp +="#X obj 0 %i cnv 15 550 15 empty empty empty 20 12 0 14 #dcdcdc #404040 0;\n" % (descHeight + 230 + 30*pcount)

            import os
            with open(os.path.join(dirname, pdname) + "-help.pd", 'w') as file:
                file.write(hlp)

        # INDEX
        hlp = "#N canvas 436 36 600 620 10;\n"
        hlp +=simple_obj(0, 0, "cnv 15 600 40 empty empty part_index 3 12 0 18 #c4dcdc #000000 0")
        for i,(f,d) in enumerate(index):
            hlp +=simple_obj(10, 50+30*i, f)
            hlp += text(200, 50+30*i, d)
        import os
        with open(os.path.join(dirname, os.path.join("..", "shape-help.pd")), 'w') as file:
            file.write(hlp)

def main():
    where = os.path.realpath(os.path.join(os.path.dirname(__file__),"../pdlib/shape"))
    generate(where)
    Msg("Pure-Data patches for Part.Shape have been written in %s\n" %where)

    where = os.path.realpath(os.path.join(os.path.dirname(__file__),"../pdhelp/shape"))
    generateHelp(where)
    Msg("Pure-Data help for Part.Shape have been written in %s\n" %where)

main()
